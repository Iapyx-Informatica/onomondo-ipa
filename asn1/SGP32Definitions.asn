-- SGP32Definitions.asn - updated to GSMA SGP.32 v1.2
-- Every change from the v1.0 baseline carries an inline marker.
-- Sources: GSMA SGP.32 v1.2 Annex C and the osmocom SGP.32 changelog.
-- Regenerate the codec with ./asn1/regenerate_libasn.sh after editing.

-- Section 2.1.3
-- UPDATE for v1.1: 2.1.3 — import fewer types from RSPDefinitions; SGP.32
-- now defines its own EUICCInfo2, ProfileInfoListResponse, StoreMetadataRequest,
-- AuthenticateClientRequest, AuthenticateResponseOk, PrepareDownloadResponse,
-- AuthenticateServerResponse, CancelSessionResponse, CancelSessionOk,
-- PendingNotification, ProfileInfo (overrides of SGP.22).
-- ASN1START
SGP32Definitions {joint-iso-itu-t(2) international-organizations(23) gsma(146) rsp(1) asn1modules(1) sgp32v1(31)}
DEFINITIONS
AUTOMATIC TAGS
EXTENSIBILITY IMPLIED ::=
BEGIN

IMPORTS Certificate, SubjectPublicKeyInfo
FROM PKIX1Explicit88 {iso(1) identified-organization(3) dod(6) internet(1) security(5) mechanisms(5) pkix(7) id-mod(0) id-pkix1-explicit(18)}
SubjectKeyIdentifier FROM PKIX1Implicit88 {iso(1) identified-organization(3) dod(6) internet(1) security(5) mechanisms(5) pkix(7) id-mod(0) id-pkix1-implicit(19)}

-- UPDATE for v1.1: 2.1.3 — slimmer import list per v1.2 Annex C.
-- Removed (now overridden locally by SGP.32): EUICCInfo2-related pieces,
-- ProfileInfoListResponse, PrepareDownloadResponse, AuthenticateServerResponse,
-- CancelSessionResponse, RetrieveNotificationsListResponse.  Each of those is
-- overridden below under an SGP32- prefixed name and the bare one was never
-- referenced, so importing it only reserved a name this module does not use.
-- NEW imports for v1.2: VendorSpecificExtension, DpProprietaryData, OperatorId,
-- NotificationConfigurationInformation, ProfileClass, IconType, ProfileState,
-- OctetTo16 (used by new ProfileInfo / StoreMetadataRequest overrides).
-- ProfileInfo is now defined locally below (SGP.32 §4.4 override).
--
-- Annex C of v1.2 also re-states EuiccSigned1, AuthenticateResponseOk,
-- ProfileInstallationResult, StoreMetadataRequest and CancelSessionOk inside the
-- SGP.32 module rather than importing them, because that module is written to
-- stand alone.  All five are textually identical to their SGP.22 originals, so
-- they are imported here instead of duplicated.  One caveat: inside the spec's
-- module EuiccSigned1.euiccInfo2 resolves to the SGP.32 EUICCInfo2, while the
-- import binds it to the SGP.22 one.  Defining it locally is not possible while
-- RSPDefinitions is compiled alongside (see the note above SGP32-EUICCInfo2).
EuiccSigned1, CancelSessionReason,
ServerSigned1, RspCapability, Iccid, TransactionId, ProfileInfoListRequest,
RulesAuthorisationTable, EUICCInfo1, DeviceInfo,
VersionType, UICCCapability, PprIds,
CertificationDataObject, Octet1, Octet16, OctetTo16, Octet32,
PrepareDownloadResponseOk, PrepareDownloadResponseError,
AuthenticateResponseOk, AuthenticateResponseError,
CtxParams1, ProfileInstallationResult, ProfileInstallationResultData,
OtherSignedNotification, EuiccSignPIR, ErrorResult, NotificationMetadata,
CancelSessionResponseOk, CancelSessionOk,
StoreMetadataRequest, SmdpSigned2, BoundProfilePackage, NotificationEvent,
VendorSpecificExtension, DpProprietaryData, OperatorId,
NotificationConfigurationInformation, ProfileClass, IconType, ProfileState
FROM RSPDefinitions {joint-iso-itu-t(2) international-organizations(23) gsma(146) rsp(1) asn1modules(1) sgp22v2(2)};
-- ASN1STOP

-- Section 2.11.1.1
-- UPDATE for v1.1: 2.11.1.1 — EuiccPackageSigned.transactionId renamed to
-- eimTransactionId; size constraint (1..128) added on eimId.
-- ASN1START
EuiccPackageRequest ::= [81] SEQUENCE { -- Tag ' BF51', #SupportedForPsmoV1.0.0#
  euiccPackageSigned EuiccPackageSigned,
  eimSignature [APPLICATION 55] OCTET STRING -- Tag '5F37'
}
EuiccPackageSigned ::= SEQUENCE {
  eimId [0] UTF8String (SIZE(1..128)), -- UPDATE for v1.1: 2.11.1.1.1 — size constraint added
  eidValue [APPLICATION 26] Octet16, -- Tag '5A'
  counterValue [1] INTEGER,
  eimTransactionId [2] TransactionId OPTIONAL, -- UPDATE for v1.1: 2.11.1.1 — renamed from transactionId
  euiccPackage EuiccPackage
}
EuiccPackage ::= CHOICE {
  psmoList SEQUENCE OF Psmo, -- #SupportedForPsmoV1.0.0#
  ecoList SEQUENCE OF Eco -- #SupportedForEcoV1.0.0#
}
-- ASN1STOP


-- Section 2.11.1.1.1
-- UPDATE for v1.1: 2.11.1.1.1 — size constraint on eimId, new indirectProfileDownload[9].
-- ASN1START
EimConfigurationData ::= SEQUENCE {
  eimId [0] UTF8String (SIZE(1..128)), -- UPDATE for v1.1: 2.11.1.1.1 — size constraint added
  eimFqdn [1] UTF8String OPTIONAL, -- FQDN of eIM
  eimIdType [2] EimIdType OPTIONAL,
  counterValue [3] INTEGER OPTIONAL, -- initial counterValue for the eIM
  associationToken [4] INTEGER OPTIONAL,
  eimPublicKeyData [5] CHOICE {
    eimPublicKey SubjectPublicKeyInfo, -- public key of eIM, used for eUICC Package signature verification, where the encoding follows X.509 standard
    eimCertificate Certificate -- certificate of eIM, used for eUICC Package signature verification, where the encoding follows X.509 standard
  } OPTIONAL,
  trustedPublicKeyDataTls [6] CHOICE {
    trustedEimPkTls SubjectPublicKeyInfo, -- public key of eIM, used for TLS or DTLS, where the encoding follows X.509 standard
    trustedCertificateTls Certificate -- either the certificate of eIM, used for (D)TLS, or the certificate of the CA, where the encoding follows X.509 standard
  } OPTIONAL,
  eimSupportedProtocol [7] EimSupportedProtocol OPTIONAL,
  euiccCiPKId [8] SubjectKeyIdentifier OPTIONAL, -- CI Public Key Identifier supported on the eUICC for signature creation
  indirectProfileDownload [9] NULL OPTIONAL -- NEW in v1.1: 2.11.1.1.1 — support of Indirect Profile download with indicated EimSupportedProtocol
}
EimIdType ::= INTEGER {
  eimIdTypeOid(1),
  eimIdTypeFqdn(2),
  eimIdTypeProprietary(3)
}
EimSupportedProtocol ::= BIT STRING {
  eimRetrieveHttps(0),
  eimRetrieveCoaps(1),
  eimInjectHttps(2),
  eimInjectCoaps(3),
  eimProprietary(4)
}
-- ASN1STOP

-- Section 2.11.1.1.2
-- ASN1START
Eco ::= CHOICE {
  addEim [8] EimConfigurationData, -- for eIM configuration data see 2.11.1
  deleteEim [9] SEQUENCE {eimId [0] UTF8String},
  updateEim [10] EimConfigurationData,
  listEim [11] SEQUENCE {}
}
-- ASN1STOP

-- Section 2.11.1.1.3
-- UPDATE for v1.1: 2.11.1.1.3 — configureAutoEnable renamed to configureImmediateEnable
-- (sub-fields renamed too); new setFallbackAttribute, unsetFallbackAttribute,
-- setDefaultDpAddress PSMOs.
-- ASN1START
Psmo ::= CHOICE {
  enable [3] SEQUENCE {
    iccid [APPLICATION 26] Iccid,
    rollbackFlag NULL OPTIONAL
  },
  disable [4] SEQUENCE {iccid [APPLICATION 26] Iccid},
  delete [5] SEQUENCE {iccid [APPLICATION 26] Iccid},
  listProfileInfo [45] ProfileInfoListRequest, -- Tag 'BF2D'
  getRAT [6] SEQUENCE {},
  -- UPDATE for v1.1: 2.11.1.1.3 — renamed configureAutoEnable -> configureImmediateEnable;
  -- autoEnableFlag -> immediateEnableFlag; smdpOid -> defaultSmdpOid;
  -- smdpAddress -> defaultSmdpAddress.
  configureImmediateEnable [7] SEQUENCE {
    immediateEnableFlag [0] NULL OPTIONAL,
    defaultSmdpOid [1] OBJECT IDENTIFIER OPTIONAL,
    defaultSmdpAddress [2] UTF8String OPTIONAL
  },
  -- NEW in v1.1: 2.11.1.1.3 — Fallback attribute PSMOs
  setFallbackAttribute [8] SEQUENCE {iccid [APPLICATION 26] Iccid},
  unsetFallbackAttribute [9] SEQUENCE {},
  -- NEW in v1.1: 2.11.1.1.3 — default SM-DP+ address PSMO
  setDefaultDpAddress [101] SGP32-SetDefaultDpAddressRequest -- Tag 'BF65'
}
-- ASN1STOP


-- Section 2.11.1.2
-- UPDATE for v1.1: 2.11.1.2 — euiccCiPKId renamed to euiccCiPKIdentifierToBeUsed
-- and TYPE CHANGED (SubjectKeyIdentifier -> OCTET STRING, possibly truncated);
-- searchCriteria renamed to searchCriteriaNotification and euiccPackageResults
-- branch removed; new searchCriteriaEuiccPackageResult [2] and eimTransactionId [3].
-- Handled in proc_euicc_data_req.c.
-- ASN1START
IpaEuiccDataRequest ::= [82] SEQUENCE { -- Tag BF52
  tagList [APPLICATION 28] OCTET STRING, -- Tag '5C'
  euiccCiPKIdentifierToBeUsed OCTET STRING OPTIONAL, -- UPDATE for v1.1: 2.11.1.2 — renamed + type changed from SubjectKeyIdentifier; CI Public Key Identifier (possibly truncated)
  searchCriteriaNotification [1] CHOICE { -- UPDATE for v1.1: 2.11.1.2 — renamed from searchCriteria; euiccPackageResults branch moved out
    seqNumber [0] INTEGER,
    profileManagementOperation [1] NotificationEvent
  } OPTIONAL,
  searchCriteriaEuiccPackageResult [2] CHOICE { -- NEW in v1.1: 2.11.1.2
    seqNumber [0] INTEGER
  } OPTIONAL,
  eimTransactionId [3] TransactionId OPTIONAL -- NEW in v1.1: 2.11.1.2 — Tag '83'
}
-- ASN1STOP

-- Section 2.11.1.3
-- (Already uses v1.1 name ProfileDownloadTriggerRequest; see osmocom changelog 2.11.1.)
-- ASN1START
ProfileDownloadTriggerRequest ::= [84] SEQUENCE { -- Tag 'BF54'
  profileDownloadData [0] ProfileDownloadData OPTIONAL,
  eimTransactionId [2] TransactionId OPTIONAL
}
ProfileDownloadData ::= CHOICE {
  activationCode [0] UTF8String (SIZE(0..255)),
  contactDefaultSmdp [1] NULL,
  contactSmds [2] SEQUENCE {
    smdsAddress UTF8String OPTIONAL
  }
}
-- ASN1STOP

-- Section 2.11.1.4
-- ASN1START
EimAcknowledgements ::= [83] SEQUENCE OF SequenceNumber -- Tag BF53
SequenceNumber ::= [0] INTEGER
-- ASN1STOP


-- Section 2.11.2.1
-- UPDATE for v1.1: 2.11.2.1 — signing change.
-- v1.0: euiccSignEPR = sign(euiccPackageResultDataSigned || eimSignature)
-- v1.2: euiccSignEPR = sign(euiccPackageResultDataSigned || associationToken)
--       (if no associationToken is configured, the value 0 is used)
-- The same change applies to euiccSignEPE over euiccPackageErrorDataSigned.
-- Both are produced with SK.EUICC.ECDSA and verified by the eIM against
-- PK.EUICC.ECDSA from CERT.EUICC.ECDSA.
--
-- No IPA-side action: this is signing done inside the eUICC, and libipa neither
-- builds the TBS nor signs anything (it contains no ECDSA signing at all).
-- The consumer-eUICC emulation does construct an EuiccPackageResult, but it
-- cannot sign one either: SK.EUICC.ECDSA never leaves the card and SGP.22 ES10
-- offers no primitive that signs caller-supplied data, only functions that sign
-- structures the eUICC composes itself.  It therefore emits a fixed 64-byte
-- placeholder (es10b_load_euicc_pkg.c), which a conforming eIM discards under
-- section 5.14.6.  That is a limitation of the emulation, not a missing TBS
-- update; see the note in load_euicc_pkg_iot_emu().
--
-- UPDATE for v1.1: 2.11.2 — many renames and additions below:
--   - transactionId -> eimTransactionId (across signed/error data types)
--   - configureAutoEnableResult -> configureImmediateEnableResult
--   - eimId constrained to (SIZE(1..128))
--   - new result branches: setFallbackAttributeResult, unsetFallbackAttributeResult,
--     setDefaultDpAddressResult
--   - EuiccPackageErrorCode: new ecallActive(104)
--   - EuiccPackageErrorUnsigned: eimTransactionId added
--   - EnableProfileResult: disallowedByPolicy(3), catBusy(5), rollbackNotAvailable(20) added
--   - DisableProfileResult: disallowedByPolicy(3), catBusy(5) added
--   - DeleteProfileResult: disallowedByPolicy(3), rollbackNotAvailable(20), returnFallbackProfile(21) added
--   - AddEimResult: associatedEimAlreadyExists(2) added
--   - ListEimResult: listEimError set reduced (commandError removed)
--   - EimIdInfo: eimIdType tag changed from [4] to [2]
--   - New types: SetFallbackAttributeResult, UnsetFallbackAttributeResult
--   - ProfileInfoListResponse used directly (was SGP32-ProfileInfoListResponse).
-- ASN1START
EuiccPackageResult ::= [81] CHOICE { -- Tag 'BF51' #SupportedForPsmoV1.0.0#
  euiccPackageResultSigned EuiccPackageResultSigned,
  euiccPackageErrorSigned EuiccPackageErrorSigned,
  euiccPackageErrorUnsigned EuiccPackageErrorUnsigned
}
EuiccPackageResultSigned ::= SEQUENCE {
  euiccPackageResultDataSigned EuiccPackageResultDataSigned,
  euiccSignEPR [APPLICATION 55] OCTET STRING -- Tag '5F37' — UPDATE for v1.1: 2.11.2.1 signing input changed (see header note)
}
EuiccPackageResultDataSigned ::= SEQUENCE { -- #SupportedForPsmoV1.0.0#
  eimId [0] UTF8String (SIZE(1..128)), -- UPDATE for v1.1: 2.11.2 — size constraint
  counterValue [1] INTEGER,
  eimTransactionId [2] TransactionId OPTIONAL, -- UPDATE for v1.1: 2.11.2 — renamed from transactionId
  seqNumber [3] INTEGER,
  euiccResult SEQUENCE OF EuiccResultData
}
EuiccResultData ::= CHOICE {
  enableResult [3] EnableProfileResult,
  disableResult [4] DisableProfileResult,
  deleteResult [5] DeleteProfileResult,
  listProfileInfoResult [45] SGP32-ProfileInfoListResponse, -- UPDATE for v1.1: 2.11.2 — SGP.32 profile-info list result; kept SGP32- prefix locally to avoid RSP import collision (v1.2 spec uses bare ProfileInfoListResponse)
  getRATResult [6] RulesAuthorisationTable, -- see SGP.22
  configureImmediateEnableResult [7] ConfigureImmediateEnableResult, -- UPDATE for v1.1: 2.11.2 — renamed from configureAutoEnableResult
  addEimResult [8] AddEimResult,
  deleteEimResult [9] DeleteEimResult,
  updateEimResult [10] UpdateEimResult,
  listEimResult [11] ListEimResult,
  rollbackResult [12] RollbackProfileResult,
  setFallbackAttributeResult [13] SetFallbackAttributeResult, -- NEW in v1.1: 2.11.2
  unsetFallbackAttributeResult [14] UnsetFallbackAttributeResult, -- NEW in v1.1: 2.11.2
  processingTerminated INTEGER {
    resultSizeOverflow(1),
    unknownOrDamagedCommand(2),
    interruption(3),
    undefinedError(127)
  },
  setDefaultDpAddressResult [101] SGP32-SetDefaultDpAddressResponse -- NEW in v1.1: 2.11.2
}
EuiccPackageErrorSigned ::= SEQUENCE {
  euiccPackageErrorDataSigned EuiccPackageErrorDataSigned,
  euiccSignEPE [APPLICATION 55] OCTET STRING -- Tag '5F37' — UPDATE for v1.1: 2.11.2.1 signing input changed (see header note)
}
EuiccPackageErrorDataSigned ::= SEQUENCE {
  eimId [0] UTF8String (SIZE(1..128)), -- UPDATE for v1.1: 2.11.2 — size constraint
  counterValue [1] INTEGER,
  eimTransactionId [2] TransactionId OPTIONAL, -- UPDATE for v1.1: 2.11.2 — renamed from transactionId
  euiccPackageErrorCode EuiccPackageErrorCode
}
EuiccPackageErrorCode ::= INTEGER {
  invalidEid(3),
  replayError(4),
  counterValueOutOfRange(6),
  sizeOverflow(15),
  ecallActive(104), -- NEW in v1.1: 2.11.2 — reject when Emergency Profile is enabled
  undefinedError(127)
}
EuiccPackageErrorUnsigned ::= SEQUENCE {
  eimId [0] UTF8String (SIZE(1..128)), -- UPDATE for v1.1: 2.11.2 — size constraint
  eimTransactionId [2] TransactionId OPTIONAL, -- NEW in v1.1: 2.11.2
  associationToken [4] INTEGER OPTIONAL
}
-- UPDATE for v1.1: 2.11.2 — renamed ConfigureAutoEnableResult -> ConfigureImmediateEnableResult
ConfigureImmediateEnableResult ::= INTEGER {
  ok(0),
  insufficientMemory(1),
  commandError(7),
  undefinedError(127)
}
EnableProfileResult ::= INTEGER {
  ok(0),
  iccidOrAidNotFound(1),
  profileNotInDisabledState(2),
  disallowedByPolicy(3), -- NEW in v1.1: 2.11.2
  catBusy(5),            -- NEW in v1.1: 2.11.2
  rollbackNotAvailable(20), -- NEW in v1.1: 2.11.2
  undefinedError(127)
}
DisableProfileResult ::= INTEGER {
  ok(0),
  iccidOrAidNotFound(1),
  profileNotInEnabledState(2),
  disallowedByPolicy(3), -- NEW in v1.1: 2.11.2
  catBusy(5),            -- NEW in v1.1: 2.11.2
  undefinedError(127)
}
DeleteProfileResult ::= INTEGER {
  ok(0),
  iccidOrAidNotFound(1),
  profileNotInDisabledState(2),
  disallowedByPolicy(3),     -- NEW in v1.1: 2.11.2
  rollbackNotAvailable(20),  -- NEW in v1.1: 2.11.2
  returnFallbackProfile(21), -- NEW in v1.1: 2.11.2
  undefinedError(127)
}
-- Section 4.4
-- SGP.32 v1.1/v1.2 override of SGP.22 ProfileInfo.  All base fields are
-- identical to SGP.22; two IoT-specific extension additions are appended:
--   fallbackAttribute [38] / Tag '9F26': TRUE if this Profile has been
--     designated as the Fallback Profile via the setFallbackAttribute PSMO
--     (§2.11.1.1.3).  Cleared by unsetFallbackAttribute.
--   fallbackAllowed [103] / Tag '9F67': the Profile Owner authorises this
--     Profile to be used by the Fallback Mechanism.
--   ecallIndication [123] / Tag '9F7B': TRUE if this Profile is the Emergency
--     Profile, set from the Profile Metadata at download (§3.2.3.1 step 12).
-- IMPORTANT: both fields are part of the TBS signed by the eUICC as
-- euiccSignEPR / euiccSignEPE (§2.11.2.1).  Any decode/re-encode path in
-- the IPAd that touches euiccPackageResultDataSigned MUST preserve them.
-- Previously the IPAd imported ProfileInfo from RSPDefinitions (SGP.22),
-- which had no named extension additions; the asn1c BER decoder therefore
-- silently dropped 9F67 and 9F7B, breaking euiccSignEPR verification at
-- the eIM.  This local definition fixes that by naming the extensions so
-- the codec stores and re-emits them faithfully.
-- The three extension additions below are transcribed from the v1.2 ProfileInfo
-- in section 4.4; earlier revisions of this file had them wrong (see git log).
-- Note that 9F26 says a Profile IS the Fallback Profile while 9F67 says the
-- Profile Owner ALLOWS it to become one. They are two different flags, and only
-- the second one gates setFallbackAttribute (section 3.4.6 step 4).
-- ASN1START
SGP32-ProfileInfo ::= [PRIVATE 3] SEQUENCE { -- Tag 'E3'
  iccid Iccid OPTIONAL,
  isdpAid [APPLICATION 15] OctetTo16 OPTIONAL, -- Tag '4F'
  profileState [112] ProfileState OPTIONAL, -- Tag '9F70'
  profileNickname [16] UTF8String (SIZE(0..64)) OPTIONAL, -- Tag '90'
  serviceProviderName [17] UTF8String (SIZE(0..32)) OPTIONAL, -- Tag '91'
  profileName [18] UTF8String (SIZE(0..64)) OPTIONAL, -- Tag '92'
  iconType [19] IconType OPTIONAL, -- Tag '93'
  icon [20] OCTET STRING (SIZE(0..1024)) OPTIONAL, -- Tag '94'
  profileClass [21] ProfileClass OPTIONAL, -- Tag '95'
  notificationConfigurationInfo [22] SEQUENCE OF NotificationConfigurationInformation OPTIONAL, -- Tag 'B6'
  profileOwner [23] OperatorId OPTIONAL, -- Tag 'B7'
  dpProprietaryData [24] DpProprietaryData OPTIONAL, -- Tag 'B8'
  profilePolicyRules [25] PprIds OPTIONAL, -- Tag '99'
  serviceSpecificDataStoredInEuicc [34] VendorSpecificExtension OPTIONAL, -- Tag 'BF22'
  ...,
  ecallIndication [123] BOOLEAN OPTIONAL, -- Tag '9F7B' — NEW in SGP.32 §4.4
  fallbackAttribute [38] BOOLEAN DEFAULT FALSE, -- Tag '9F26' — NEW in SGP.32 §4.4: this Profile is the Fallback Profile
  fallbackAllowed [103] BOOLEAN OPTIONAL -- Tag '9F67' — NEW in SGP.32 §4.4: the Profile Owner authorises Fallback
}
-- ASN1STOP

-- UPDATE for v1.1: 2.11.2 — SGP.32 defines its own ProfileInfoListResponse
-- /Error, over its own ProfileInfo (section 4.4).  The v1.2 spec uses the bare
-- name; the SGP32- prefix here is permanent, and dropping the RSP import does
-- not help, because asn1c refuses two definitions of one name across the
-- modules it compiles together (see the note above SGP32-EUICCInfo2).  The bare
-- name is no longer imported: nothing in this module refers to the SGP.22 type.
SGP32-ProfileInfoListResponse ::= [45] CHOICE {
  profileInfoListOk SEQUENCE OF SGP32-ProfileInfo, -- SGP.32 §4.4 local override
  profileInfoListError SGP32-ProfileInfoListError
}
SGP32-ProfileInfoListError ::= INTEGER {
  incorrectInputValues(1),
  profileChangeOngoing (11),
  undefinedError(127)
}
RollbackProfileResult ::= INTEGER {
  ok(0),
  undefinedError(127)
}
-- NEW in v1.1: 2.11.2
SetFallbackAttributeResult ::= INTEGER {
  ok(0),
  iccidOrAidNotFound(1),
  fallbackNotAllowed(2),
  fallbackProfileEnabled(3),
  undefinedError(127)
}
-- NEW in v1.1: 2.11.2
UnsetFallbackAttributeResult ::= INTEGER {
  ok(0),
  noFallbackAttribute(2),
  fallbackProfileEnabled(3),
  commandError(7),
  undefinedError(127)
}
AddEimResult ::= CHOICE {
  associationToken [4] INTEGER,
  addEimResultCode INTEGER {
    ok(0),
    insufficientMemory(1),
    associatedEimAlreadyExists(2), -- NEW in v1.1: 2.11.2
    ciPKUnknown(3),
    invalidAssociationToken(5),
    counterValueOutOfRange(6),
    commandError(7),
    undefinedError(127)
  }
}
DeleteEimResult ::= INTEGER {
  ok(0),
  eimNotFound(1),
  lastEimDeleted(2), -- no eIM Configuration Data available in eUICC,
  commandError(7),
  undefinedError(127)
}
UpdateEimResult ::= INTEGER {
  ok(0),
  eimNotFound (1),
  ciPKUnknown(3),
  counterValueOutOfRange(6),
  commandError(7),
  undefinedError(127)
}
ListEimResult ::= CHOICE {
  eimIdList SEQUENCE OF EimIdInfo,
  listEimError INTEGER {
    -- UPDATE for v1.1: 2.11.2 — commandError(7) removed; only undefinedError remains
    undefinedError(127)
  }
}
EimIdInfo ::= SEQUENCE {
  eimId [0] UTF8String (SIZE(1..128)), -- UPDATE for v1.1: 2.11.2 — size constraint
  eimIdType [2] EimIdType OPTIONAL -- UPDATE for v1.1: 2.11.2 — tag changed from [4] to [2]
}
-- ASN1STOP

-- Section 2.11.2.2
-- UPDATE for v1.1: 2.11.2.2 — MAJOR restructure of IpaEuiccDataResponse.
-- - New wrapper type IpaEuiccDataResponseError (replaces the inline CHOICE error).
-- - New named IpaEuiccDataErrorCode (adds ecallActive(104)).
-- - New SGP32-PendingNotificationList and EuiccPackageResultList aliases.
-- - IpaEuiccData completely restructured: new tag assignments, field reorder,
--   notificationsList moved to [0], defaultSmdpAddress [1], euiccPackageResultList [2]
--   added, euiccInfo2 now uses bare EUICCInfo2 (no SGP32- prefix), new eimTransactionId [7].
-- proc_euicc_data_req.c builds and consumes the new structure.
-- ASN1START
IpaEuiccDataErrorCode ::= INTEGER { -- NEW in v1.1: 2.11.2.2 — extracted named type
  incorrectTagList(1),
  euiccCiPKIdNotFound(5),
  ecallActive(104), -- NEW in v1.1
  undefinedError(127)
}
IpaEuiccDataResponseError ::= SEQUENCE { -- NEW in v1.1: 2.11.2.2
  eimTransactionId [0] TransactionId OPTIONAL,
  ipaEuiccDataErrorCode IpaEuiccDataErrorCode
}
IpaEuiccDataResponse ::= [82] CHOICE { -- Tag 'BF52'
  ipaEuiccData IpaEuiccData,
  ipaEuiccDataResponseError IpaEuiccDataResponseError -- UPDATE for v1.1: 2.11.2.2 — was inline INTEGER; now uses wrapper type
}
SGP32-PendingNotificationList ::= SEQUENCE OF SGP32-PendingNotification -- NEW in v1.1: 2.11.2.2 alias
EuiccPackageResultList ::= SEQUENCE OF EuiccPackageResult   -- NEW in v1.1: 2.11.2.2 alias
IpaEuiccData ::= SEQUENCE {
  notificationsList [0] SGP32-PendingNotificationList OPTIONAL, -- UPDATE for v1.1: 2.11.2.2 — moved to tag [0]; uses new alias; was [43] SGP32-RetrieveNotificationsListResponse
  defaultSmdpAddress [1] UTF8String OPTIONAL, -- UPDATE for v1.1: 2.11.2.2 — tag changed from [0] to [1]
  euiccPackageResultList [2] EuiccPackageResultList OPTIONAL, -- NEW in v1.1: 2.11.2.2
  euiccInfo1 [32] EUICCInfo1 OPTIONAL, -- Tag 'BF20'
  euiccInfo2 [34] SGP32-EUICCInfo2 OPTIONAL, -- Tag 'BF22' — UPDATE for v1.1: 2.11.2.2 — kept SGP32- prefix (see note at SGP32-EUICCInfo2 definition)
  rootSmdsAddress [3] UTF8String OPTIONAL, -- Tag '83'
  associationToken [4] INTEGER OPTIONAL, -- Tag '84'
  eumCertificate [5] Certificate OPTIONAL, -- Tag 'A5'
  euiccCertificate [6] Certificate OPTIONAL, -- Tag 'A6'
  eimTransactionId [7] TransactionId OPTIONAL, -- NEW in v1.1: 2.11.2.2
  ipaCapabilities [8] IpaCapabilities OPTIONAL, -- Tag 'A8' — UPDATE for v1.1: 2.11.2.2 — tag changed from '88' to 'A8' (constructed)
  deviceInfo [9] DeviceInfo OPTIONAL -- Tag 'A9'
}
-- ASN1STOP

-- Section 2.11.2.3
-- UPDATE for v1.1: 2.11.2.3 — profileDownloadError now carries profileDownloadErrorReason.
-- ASN1START
ProfileDownloadTriggerResult ::= [84] SEQUENCE { -- tag 'BF54'
  eimTransactionId [2] TransactionId OPTIONAL,
  profileDownloadTriggerResultData CHOICE {
    profileInstallationResult [55] ProfileInstallationResult, -- UPDATE for v1.1: 2.11.2.3 — in v1.0 this used a local SGP32- prefixed copy, since removed as an exact duplicate of the import
    profileDownloadError SEQUENCE {
      profileDownloadErrorReason [0] INTEGER { -- NEW in v1.1: 2.11.2.3
        ecallActive(104),
        undefinedError(127)
      },
      errorResponse OCTET STRING OPTIONAL
    }
  }
}
-- ASN1STOP

-- NEW in v1.1: 3.8.4 — ISD-R Selection and IPAe Activation
-- ISDRProprietaryApplicationTemplateIoT is read from the ISD-R SELECT FCI in
-- libipa/euicc.c; IpaeActivationRequest/Response are used by libipa/ipae_activation.c.
-- ASN1START
ISDRProprietaryApplicationTemplateIoT ::= [PRIVATE 1] SEQUENCE { -- Tag 'E1'
  euiccConfiguration BIT STRING {
    ipaeSupported(0), -- IPA in the eUICC (IPAe) supported
    enabledProfile(1) -- eUICC contains an Enabled Profile
  }
}
IpaeActivationRequest ::= [66] SEQUENCE { -- Tag 'BF42'
  ipaeOption BIT STRING {
    activateIpae(0) -- IPAe activation
  }
}
IpaeActivationResponse ::= [66] SEQUENCE { -- Tag 'BF42'
  ipaeActivationResult INTEGER {ok(0), notSupported(1)}
}
-- ASN1STOP

-- Section 4.1
-- ASN1START
IpaCapabilities ::= SEQUENCE {
  ipaFeatures [0] BIT STRING {
    directRspServerCommunication (0),
    indirectRspServerCommunication (1),
    eimDownloadDataHandling (2),
    eimCtxParams1Generation (3),
    eimProfileMetadataVerification (4),
    minimizeEsipaBytes (5)
  },
  ipaSupportedProtocols [1] BIT STRING {
    ipaRetrieveHttps(0),
    ipaRetrieveCoaps(1),
    ipaInjectHttps(2),
    ipaInjectCoaps(3),
    ipaProprietary(4)
  } OPTIONAL
}
-- ASN1STOP

-- Section 5.9.2
-- UPDATE for v1.1: 5.9.2 — SGP.32 EUICCInfo2 gains three OPTIONAL fields.
--  - rfu2/rfu3/rfu4 renamed to euiccCiPKIdListForSigningV3 [17],
--    additionalEuiccInfo [18], highestSvn [19].
-- NEW in v1.1: 5.9.2 — IoTSpecificInfo.ecallSupported, .fallbackSupported.
-- Both are surfaced to the API consumer by ipa_get_euicc_caps() (ipad.h).
-- NOTE: this is the canonical explanation of every SGP32- prefix in this file.
-- The v1.2 spec uses bare names throughout, because its module stands alone.
-- Here RSPDefinitions.asn is compiled in the same asn1c pass, because libipa
-- needs the SGP.22 codecs too (that being the whole point of the consumer-eUICC
-- emulation), and asn1c puts every module's types into one flat C namespace, one
-- file per type name.  Two definitions of one name are a hard error:
--
--   FATAL: ASN.1 expression "X" at line N of module SGP32Definitions
--   clashes with expression "X" at line M of module RSPDefinitions
--
-- The IMPORTS list has nothing to do with it: the clash is between the two
-- *definitions*, so pruning the import does not enable the rename.  Wherever the
-- SGP.32 type genuinely differs from its SGP.22 namesake, the prefix therefore
-- stays for as long as both modules are compiled together.  Where the two are
-- textually identical (ProfileInstallationResult, CancelSessionOk) there is no
-- local copy at all and the imported type is used directly.
-- ASN1START
SGP32-EUICCInfo2 ::= [34] SEQUENCE { -- Tag 'BF22' — SGP.32 override; the bare name is defined by RSPDefinitions, see the note above
  profileVersion [1] VersionType, -- Base eUICC Profile package version supported
  svn [2] VersionType, -- GSMA SGP.22 version supported (SVN) referenced by SGP.32
  euiccFirmwareVer [3] VersionType, -- eUICC Firmware version
  extCardResource [4] OCTET STRING, -- Extended Card Resource Information according to ETSI TS 102 226
  uiccCapability [5] UICCCapability,
  ts102241Version [6] VersionType OPTIONAL,
  globalplatformVersion [7] VersionType OPTIONAL,
  rspCapability [8] RspCapability,
  euiccCiPKIdListForVerification [9] SEQUENCE OF SubjectKeyIdentifier,
  euiccCiPKIdListForSigning [10] SEQUENCE OF SubjectKeyIdentifier,
  euiccCategory [11] INTEGER {
    other(0),
    basicEuicc(1),
    mediumEuicc(2),
    contactlessEuicc(3)
  } OPTIONAL,
  forbiddenProfilePolicyRules [25] PprIds OPTIONAL, -- Tag '99'
  ppVersion VersionType, -- Protection Profile version
  sasAcreditationNumber UTF8String (SIZE(0..64)),
  certificationDataObject [12] CertificationDataObject OPTIONAL,
  treProperties [13] BIT STRING {
    isDiscrete(0),
    isIntegrated(1),
    usesRemoteMemory(2) -- refers to remote memory protected per SGP.21
  } OPTIONAL,
  treProductReference [14] UTF8String OPTIONAL,
  additionalEuiccProfilePackageVersions [15] SEQUENCE OF VersionType OPTIONAL,
  ipaMode [16] IpaMode OPTIONAL,
  euiccCiPKIdListForSigningV3 [17] SEQUENCE OF SubjectKeyIdentifier OPTIONAL, -- UPDATE for v1.1: 5.9.2 — renamed from rfu2; not used in v1.2 but field is defined
  additionalEuiccInfo [18] OCTET STRING (SIZE(0..32)) OPTIONAL, -- UPDATE for v1.1: 5.9.2 — renamed from rfu3; not used in v1.2
  highestSvn [19] VersionType OPTIONAL, -- UPDATE for v1.1: 5.9.2 — renamed from rfu4; not used in v1.2
  iotSpecificInfo [20] IoTSpecificInfo OPTIONAL -- mandatory within SGP.32
}
IoTSpecificInfo ::= SEQUENCE {
  iotVersion [0] SEQUENCE OF VersionType, -- SGP.32 version(s) supported by the eUICC, at least one must be present
  ecallSupported [1] NULL OPTIONAL, -- NEW in v1.1: 5.9.2 — present iff eUICC supports Emergency Profile mechanism
  fallbackSupported [2] NULL OPTIONAL -- NEW in v1.1: 5.9.2 — present iff eUICC supports Fallback mechanism
}
IpaMode ::= INTEGER {
  ipad (0), -- IPAd is active
  ipae (1) -- IPAe is active
}
-- ASN1STOP

-- Section 5.9.4
-- UPDATE for v1.2: CR12010R00 — clarified behaviour when optional
-- EimConfigurationData subfields are absent (no schema change, libipa-side only).
-- Handled in libipa/es10b_add_init_eim.c: eimIdType, eimSupportedProtocol and
-- euiccCiPKId get the defaults the eUICC is mandated to assign; eimFqdn and
-- trustedPublicKeyDataTls stay absent because no default is mandated for them.
-- ASN1START
AddInitialEimRequest ::= [87] SEQUENCE { -- Tag 'BF57'
  eimConfigurationDataList [0] SEQUENCE OF EimConfigurationData
}
-- ASN1STOP
-- UPDATE for v1.1: 5.9.4 — AddInitialEimResponse adds associatedEimAlreadyExists(2).
-- ASN1START
AddInitialEimResponse ::= [87] CHOICE { -- Tag 'BF57'
  addInitialEimOk SEQUENCE OF CHOICE {
    associationToken [4] INTEGER,
    addOk NULL
  },
  addInitialEimError INTEGER {
    insufficientMemory(1),
    associatedEimAlreadyExists(2), -- NEW in v1.1: 5.9.4 (replaces former unsignedEimConfigDisallowed(2))
    ciPKUnknown(3),
    invalidAssociationToken(5),
    counterValueOutOfRange(6),
    commandError(7),
    undefinedError(127)
  }
}
-- ASN1STOP

-- Section 5.9.5
-- UPDATE for v1.1: 5.9.5 — EuiccMemoryReset restructured.  Tag changed from
-- [52] (BF34) to [100] (BF64).  New resetOptions bits deletePreLoadedTestProfiles(3),
-- deleteProvisioningProfiles(4); resetEimConfigData moved to (5); new
-- resetImmediateEnableConfig(6).  Added ecallActive(104) to resetResult.
-- Renamed resetAutoEnableConfigResult -> resetImmediateEnableConfigResult.
-- NOTE: we KEEP the SGP32- prefix on these types because RSPDefinitions (SGP.22)
-- defines bare EuiccMemoryResetRequest/Response with a DIFFERENT tag [52].
-- Spec v1.2 uses bare names; unifying would require dropping the RSP import.
-- (added manually since the PDF document lacks the ASN1START/ASN1STOP token for this function)
SGP32-EuiccMemoryResetRequest ::= [100] SEQUENCE { -- Tag 'BF64' — UPDATE for v1.1: 5.9.5 — tag [52] -> [100]
  resetOptions [2] BIT STRING {
    deleteOperationalProfiles(0),
    deleteFieldLoadedTestProfiles(1),
    resetDefaultSmdpAddress(2),
    deletePreLoadedTestProfiles(3),  -- NEW in v1.1: 5.9.5
    deleteProvisioningProfiles(4),   -- NEW in v1.1: 5.9.5
    resetEimConfigData(5),           -- UPDATE for v1.1: 5.9.5 — was bit 3
    resetImmediateEnableConfig(6)    -- UPDATE for v1.1: 5.9.5 — renamed from resetAutoEnableConfig; was bit 4
  }
}
SGP32-EuiccMemoryResetResponse ::= [100] SEQUENCE { -- Tag 'BF64' — UPDATE for v1.1: 5.9.5
  resetResult INTEGER {ok(0), nothingToDelete(1), catBusy(5), ecallActive(104), undefinedError(127)}, -- NEW in v1.1: ecallActive(104)
  resetEimResult INTEGER {ok(0), nothingToDelete(1), eimResetNotSupported(2), undefinedError(127)} OPTIONAL, -- UPDATE for v1.1: 5.9.5 — untagged (was [1])
  resetImmediateEnableConfigResult INTEGER {ok(0), resetIECNotSupported(1), undefinedError(127)} OPTIONAL -- UPDATE for v1.1: 5.9.5 — renamed from resetAutoEnableConfigResult; untagged (was [2])
}

-- Section 5.9.10
-- ASN1START
GetCertsRequest ::= [86] SEQUENCE { -- Tag 'BF56'
  euiccCiPKId SubjectKeyIdentifier OPTIONAL -- CI Public Key Identifier supported on the eUICC for signature creation
}
-- ASN1STOP
-- ASN1START
GetCertsResponse ::= [86] CHOICE { -- Tag 'BF56'
  certs SEQUENCE {
    eumCertificate [5] Certificate, -- Tag 'A5'
    euiccCertificate [6] Certificate -- Tag 'A6'
  },
  getCertsError INTEGER {invalidCiPKId(1), undfinedError(127)}
}
-- ASN1STOP

-- Section 5.9.11
-- UPDATE for v1.1: 5.9.11 — restructured.  Removed notificationAndEprList branch;
-- other branches now use SGP32-PendingNotificationList / EuiccPackageResultList aliases.
-- Renamed SGP32-RetrieveNotificationsListRequest/Response -> plain names.
-- es10b_retr_notif_from_lst.c no longer references the removed branch.
-- NOTE: kept SGP32- prefix; RSPDefinitions has a bare RetrieveNotificationsListRequest.
SGP32-RetrieveNotificationsListRequest ::= [43] SEQUENCE { -- Tag 'BF2B'
  searchCriteria CHOICE {
    seqNumber [0] INTEGER,
    profileManagementOperation [1] NotificationEvent,
    euiccPackageResults [2] NULL
  } OPTIONAL
}
-- NOTE: the spec names the type below RetrieveNotificationsListResponse.  The
-- SGP32- prefix is permanent, and removing the RSP import does not help: asn1c
-- compiles RSPDefinitions and this module in one pass into a single flat C
-- namespace, and refuses two definitions of one name outright (see the note
-- above SGP32-EUICCInfo2).  The bare name is no longer imported, since nothing
-- in this module refers to the SGP.22 type.
-- ASN1START
SGP32-RetrieveNotificationsListResponse ::= [43] CHOICE { -- Tag 'BF2B' — UPDATE for v1.1: 5.9.11 — spec name is RetrieveNotificationsListResponse; see the note above
  notificationList SGP32-PendingNotificationList, -- UPDATE for v1.1: 5.9.11 — use alias instead of inline SEQUENCE OF
  notificationsListResultError INTEGER { undefinedError(127)},
  euiccPackageResultList EuiccPackageResultList -- UPDATE for v1.1: 5.9.11 — use alias; notificationAndEprList branch REMOVED
}
-- ASN1STOP

-- Section 5.9.15
-- UPDATE for v1.1: 5.9.15 — EnableUsingDD renamed to ImmediateEnable.
-- Now carries mandatory refreshFlag BOOLEAN.
-- UPDATE for v1.2: CR111007R00 — on ImmediateEnable, rollback authorization MUST
-- also be reset when refreshFlag == true (behavioral; see proc_euicc_pkg_dwnld_exec.c).
-- Implemented in libipa/es10b_immediate_enable.{c,h}, which replaced the v1.0
-- es10b_enable_using_dd.c.
-- ASN1START
ImmediateEnableRequest ::= [90] SEQUENCE { -- Tag 'BF5A' — UPDATE for v1.1: 5.9.15 — renamed from EnableUsingDDRequest
  refreshFlag BOOLEAN -- NEW in v1.1: 5.9.15 — indicating whether REFRESH is required
}
-- ASN1STOP
-- ASN1START
ImmediateEnableResponse ::= [90] SEQUENCE { -- Tag 'BF5A' — UPDATE for v1.1: 5.9.15 — renamed from EnableUsingDDResponse
  immediateEnableResult [0] INTEGER { -- UPDATE for v1.1: 5.9.15 — renamed from enableUsingDDResult
    ok(0),
    immediateEnableNotAvailable(1), -- UPDATE for v1.1: 5.9.15 — renamed from autoEnableNotAvailable
    noSessionContext(4),
    catBusy(5), -- NEW in v1.1: 5.9.15
    undefinedError(127)
  }
}
-- ASN1STOP

-- Section 5.9.16
-- ASN1START
ProfileRollbackRequest ::= [88] SEQUENCE { -- Tag 'BF58'
  refreshFlag BOOLEAN -- indicating whether REFRESH is required
}
-- ASN1STOP
-- ASN1START
ProfileRollbackResponse ::= [88] SEQUENCE { -- Tag 'BF58'
  cmdResult INTEGER {
    ok(0),
    rollbackNotAllowed(1), -- Usage of rollback was not granted by the eIM
    catBusy(5),
    commandError(7),
    undefinedError(127)
  },
  eUICCPackageResult [81] EuiccPackageResult OPTIONAL
}
-- ASN1STOP

-- Section 5.9.17
-- UPDATE for v1.1: 5.9.17 — ConfigureAutoProfileEnabling renamed to
-- ConfigureImmediateProfileEnabling; sub-fields renamed (see 2.11.1.1.3).
-- Response error set changed: removed unsignedAutoEnableConfigDisallowed,
-- added associatedEimAlreadyExists.
-- Used by libipa/es10b_cfg_immediate_enable.c for the IPA-driven call; the same
-- configuration also arrives eIM-driven through Psmo.configureImmediateEnable.
-- ASN1START
ConfigureImmediateProfileEnablingRequest ::= [89] SEQUENCE { -- Tag 'BF59' — UPDATE for v1.1: 5.9.17 — renamed
  immediateEnableFlag [0] NULL OPTIONAL,      -- UPDATE for v1.1: 5.9.17 — renamed from autoEnableFlag
  defaultSmdpOid [1] OBJECT IDENTIFIER OPTIONAL, -- UPDATE for v1.1: 5.9.17 — renamed from smdpOid
  defaultSmdpAddress [2] UTF8String OPTIONAL  -- UPDATE for v1.1: 5.9.17 — renamed from smdpAddress
}
-- ASN1STOP
-- ASN1START
ConfigureImmediateProfileEnablingResponse ::= [89] SEQUENCE { -- Tag 'BF59' — UPDATE for v1.1: 5.9.17 — renamed
  configImmediateEnableResult [0] INTEGER { -- UPDATE for v1.1: 5.9.17 — renamed from configAutoEnableResult
    ok(0),
    insufficientMemory(1),
    associatedEimAlreadyExists(2), -- NEW in v1.1: 5.9.17 (replaces unsignedAutoEnableConfigDisallowed(2))
    undefinedError(127)
  }
}
-- ASN1STOP

-- Section 5.9.18
-- UPDATE for v1.1: 5.9.18 — GetEimConfigurationDataRequest now has searchCriteria
-- CHOICE { eimId [0] UTF8String (SIZE(1..128)) } OPTIONAL.
-- ASN1START
GetEimConfigurationDataRequest ::= [85] SEQUENCE { -- Tag 'BF55'
  searchCriteria CHOICE {                       -- NEW in v1.1: 5.9.18
    eimId [0] UTF8String (SIZE(1..128))
  } OPTIONAL
}
-- ASN1STOP
-- ASN1START
GetEimConfigurationDataResponse ::= [85] SEQUENCE { -- Tag 'BF55'
  eimConfigurationDataList [0] SEQUENCE OF EimConfigurationData
}
-- ASN1STOP

-- NEW in v1.1: 5.9.20 — ExecuteFallbackMechanism (ES10b).
-- Implemented in libipa/es10b_execute_fallback.{c,h}; host must decide when to
-- invoke it (e.g. on radio-registration failure of the enabled profile).
-- ASN1START
ExecuteFallbackMechanismRequest ::= [93] SEQUENCE { -- Tag 'BF5D'
  refreshFlag BOOLEAN
}
ExecuteFallbackMechanismResponse ::= [93] SEQUENCE { -- Tag 'BF5D'
  executeFallbackMechanismResult [0] INTEGER {
    ok(0),
    profileNotInDisabledState(2),
    catBusy(5),
    fallbackNotAvailable(6), -- Fallback Attribute not set
    commandError(7),
    ecallActive(104),
    undefinedError(127)
  }
}
-- ASN1STOP

-- NEW in v1.1: 5.9.21 — ReturnFromFallback (ES10b).
-- Implemented in libipa/es10b_return_from_fallback.{c,h}.
-- ASN1START
ReturnFromFallbackRequest ::= [94] SEQUENCE { -- Tag 'BF5E'
  refreshFlag BOOLEAN
}
ReturnFromFallbackResponse ::= [94] SEQUENCE { -- Tag 'BF5E'
  returnFromFallbackResult [0] INTEGER {
    ok(0),
    catBusy(5),
    fallbackNotAvailable(6),
    commandError(7),
    undefinedError(127)
  }
}
-- ASN1STOP

-- NEW in v1.1: 5.9.22 — EnableEmergencyProfile (ES10b).
-- Implemented in libipa/es10b_enable_emergency_profile.{c,h}.
-- UPDATE for v1.2: CR111007R00 — reset rollback authorization when refreshFlag == true.
-- ASN1START
EnableEmergencyProfileRequest ::= [91] SEQUENCE { -- Tag 'BF5B'
  refreshFlag BOOLEAN
}
EnableEmergencyProfileResponse ::= [91] SEQUENCE { -- Tag 'BF5B'
  enableEmergencyProfileResult [0] INTEGER {
    ok(0),
    profileNotInDisabledState(2),
    catBusy(5),
    ecallNotAvailable(8), -- Emergency Profile does not exist
    undefinedError(127)
  }
}
-- ASN1STOP

-- NEW in v1.1: 5.9.23 — DisableEmergencyProfile (ES10b).
-- Implemented in libipa/es10b_disable_emergency_profile.{c,h}.
-- UPDATE for v1.2: CR111007R00 — reset rollback authorization when refreshFlag == true.
-- ASN1START
DisableEmergencyProfileRequest ::= [92] SEQUENCE { -- Tag 'BF5C'
  refreshFlag BOOLEAN
}
DisableEmergencyProfileResponse ::= [92] SEQUENCE { -- Tag 'BF5C'
  disableEmergencyProfileResult [0] INTEGER {
    ok(0),
    profileNotInEnabledState(2),
    catBusy(5),
    undefinedError(127)
  }
}
-- ASN1STOP

-- NEW in v1.1: 5.9.24 — GetConnectivityParameters (ES10b).
-- Implemented in libipa/es10b_get_connectivity_params.{c,h}; host must thread the
-- returned httpParams into http.c / esipa.c configuration.
-- ASN1START
GetConnectivityParametersRequest ::= [95] SEQUENCE { -- Tag 'BF5F'
}
GetConnectivityParametersResponse ::= [95] CHOICE { -- Tag 'BF5F'
  connectivityParameters ConnectivityParameters,
  connectivityParametersError ConnectivityParametersError
}
ConnectivityParameters ::= SEQUENCE { -- Also used for CoAP
  httpParams [1] OCTET STRING OPTIONAL
}
ConnectivityParametersError ::= INTEGER {
  parametersNotAvailable(1),
  undefinedError(127)
}
-- ASN1STOP

-- NEW in v1.1: 5.9.25 — SetDefaultDpAddress (ES10b).
-- Referenced both as a standalone ES10b function and as a Psmo member (see 2.11.1.1.3).
-- Implemented in libipa/es10b_set_default_dp_addr.{c,h} for direct host use.
-- ASN1START
SGP32-SetDefaultDpAddressRequest ::= [101] SEQUENCE { -- Tag 'BF65'
  defaultDpAddress UTF8String -- Default SM-DP+ address as an FQDN
}
SGP32-SetDefaultDpAddressResponse ::= [101] SEQUENCE { -- Tag 'BF65'
  setDefaultDpAddressResult INTEGER { ok(0), undefinedError(127) }
}
-- ASN1STOP

-- Section 5.14.2
-- UPDATE for v1.1: 5.14.2 — the spec names this type PrepareDownloadResponse.
-- SGP.32 adds the compact branch, so it is a different type from the SGP.22 one
-- and the SGP32- prefix is permanent (see the note above SGP32-EUICCInfo2).
-- ASN1START
SGP32-PrepareDownloadResponse ::= [33] CHOICE { -- Tag 'BF21' — spec name is PrepareDownloadResponse; see the note above
  downloadResponseOk PrepareDownloadResponseOk,
  downloadResponseError PrepareDownloadResponseError,
  compactDownloadResponseOk CompactPrepareDownloadResponseOk
}
CompactPrepareDownloadResponseOk ::= SEQUENCE {
  compactEuiccSigned2 CompactEuiccSigned2, -- Compact version of EuiccSigned2
  euiccSignature2 [APPLICATION 55] OCTET STRING -- tag '5F37' signature on EuiccSigned2
}
CompactEuiccSigned2 ::= SEQUENCE {
  euiccOtpk [APPLICATION 73] OCTET STRING OPTIONAL, -- otPK.EUICC.ECKA, tag '5F49' euiccOtpk is always present except if bppEuiccOtpk was chosen by the eUICC
  hashCc Octet32 OPTIONAL -- Hash of confirmation code, if not received from eIM
}
-- ASN1STOP

-- Section 5.14.3
-- UPDATE for v1.1: 5.14.3 — v1.2 Annex C re-states EuiccSigned1 inside the
-- SGP.32 module.  Its text is identical to the SGP.22 one, so the import is kept
-- rather than duplicating it, which asn1c would refuse anyway.  The one semantic
-- difference: inside the spec's module EuiccSigned1.euiccInfo2 resolves to the
-- SGP.32 EUICCInfo2, whereas the import binds it to the SGP.22 EUICCInfo2, which
-- has no extension marker and stops at additionalEuiccProfilePackageVersions
-- [15].  A real IoT eUICC sends [16]..[20] as well, iotSpecificInfo [20] being
-- mandatory in SGP.32.  asn1c accepts that input against the SGP.22 type and
-- silently discards the trailing fields, so a decode/re-encode round-trip would
-- shorten euiccSigned1 and invalidate euiccSignature1 at the SM-DP+.
--
-- That round-trip does not happen: ipa_es10b_auth_serv() keeps the raw BER of
-- every successful response and proc_cmn_mtl_auth.c forwards it verbatim, so the
-- signed bytes reach the SM-DP+ exactly as the eUICC produced them.  The loss is
-- therefore latent, not active, but it is the reason that raw path must stay.
-- UPDATE for v1.1: 5.14.3 — AuthenticateClient procedure description changed.
-- Reviewed against v1.2: almost all of 5.14.3 binds the eIM, and the IPA-side
-- obligations are met.  transactionId is optional when smdpSigned2 is present
-- and esipa_auth_clnt.c falls back to the signed copy; hashCc is optional and
-- reaches PrepareDownload (proc_prfle_dwnld.c); profileMetaData arrives because
-- this IPA leaves IPA Capability eimProfileMetadataVerification cleared, meaning
-- it verifies the metadata itself, which ipa_ppr_verify_metadata() does.
-- Two things are deliberately not done.  compactAuthenticateResponseOk needs IPA
-- Capability minimizeEsipaBytes, which is unimplemented.  And
-- AuthenticateClientOkDSEsipa.profileDownloadTrigger [84] is decoded but never
-- read, because the SM-DS branch as a whole is unimplemented:
-- proc_indirect_prfle_dwnld.c requires authenticateClientOkDPEsipa and stops
-- otherwise.  Both belong to those features, not to this section.
-- ASN1START
SGP32-AuthenticateServerResponse ::= [56] CHOICE { -- Tag 'BF38' — spec name is AuthenticateServerResponse; SGP.32 adds the compact branch, so the prefix is permanent (see the note above SGP32-EUICCInfo2)
  authenticateResponseOk AuthenticateResponseOk,
  authenticateResponseError AuthenticateResponseError,
  compactAuthenticateResponseOk CompactAuthenticateResponseOk
}
CompactAuthenticateResponseOk ::= SEQUENCE {
  signedData CHOICE {
    euiccSigned1 EuiccSigned1,
    compactEuiccSigned1 [0] CompactEuiccSigned1 -- Compact version of EuiccSigned1
  },
  euiccSignature1 [APPLICATION 55] OCTET STRING, -- tag 5F37 signature on EuiccSigned1
  euiccCertificate [1] Certificate OPTIONAL, -- eUICC Certificate (CERT.EUICC.ECDSA)
  eumCertificate [2] Certificate OPTIONAL -- EUM Certificate (CERT.EUM.ECDSA)
}
CompactEuiccSigned1 ::= SEQUENCE {
  extCardResource [4] OCTET STRING, -- Extended Card Resource Information according to ETSI TS 102 226 extracted from euiccInfo2,
  ctxParams1 [2] CtxParams1 OPTIONAL -- ctxParams1 may be left out by IPA if eIM ctxParams1 was received from the eIM
}
-- ASN1STOP

-- Section 5.14.7
-- UPDATE for v1.1: 5.14.7 — the spec names this type PendingNotification.  The
-- SGP32- prefix is permanent: SGP.32 adds the two compact branches, so this is a
-- genuinely different type from the SGP.22 PendingNotification, and both are
-- compiled into one flat C namespace (see the note above SGP32-EUICCInfo2).
-- The spec's ProfileInstallationResult, by contrast, is textually identical to
-- the SGP.22 one, so the imported type is used directly and no local override or
-- prefix is needed.
-- UPDATE for v1.2: CR12008R01 — CompactOtherSignedNotification gains eidValue
-- (OPTIONAL) so the eIM can identify the related eUICC.
-- ASN1START
SGP32-PendingNotification ::= CHOICE { -- spec name is PendingNotification; see the note above
  profileInstallationResult [55] ProfileInstallationResult, -- tag 'BF37'
  otherSignedNotification OtherSignedNotification,
  compactProfileInstallationResult [0] CompactProfileInstallationResult,
  compactOtherSignedNotification [1] CompactOtherSignedNotification
}
CompactProfileInstallationResult ::= SEQUENCE {
  compactProfileInstallationResultData [0] CompactProfileInstallationResultData,
  euiccSignPIR EuiccSignPIR
}
CompactProfileInstallationResultData ::= SEQUENCE {
  transactionId [0] TransactionId, -- The TransactionID generated by the SM-DP+
  seqNumber INTEGER,
  iccidPresent BOOLEAN DEFAULT TRUE,
  compactFinalResult [2] CHOICE {
    compactSuccessResult CompactSuccessResult,
    errorResult ErrorResult
  }
}
CompactSuccessResult ::= SEQUENCE {
  compactAid [APPLICATION 15] OCTET STRING (SIZE (2)), -- Byte 14 and 15 of ISD-P AID
  simaResponse OCTET STRING OPTIONAL -- MUST be present if the simaResponse value (EUICCResponse) is different from the 9-byte value '30 07 A0 05 30 03 80 01 00' representing success
}
CompactOtherSignedNotification ::= SEQUENCE {
  eidValue [APPLICATION 26] Octet16 OPTIONAL, -- NEW in v1.2: CR12008R01 — Tag '5A'; lets the eIM identify the related eUICC. Recommended (not required) by 5.14.7, and only where no underlying transport already identifies the EID. Unused by libipa: the compact forms are only built by an IPA declaring minimizeEsipaBytes, which this one does not.
  tbsOtherNotification NotificationMetadata,
  euiccNotificationSignature [APPLICATION 55] OCTET STRING -- eUICC signature of tbsOtherNotification, Tag '5F37'
}
-- ASN1STOP

-- Section 5.14.8
-- UPDATE for v1.1: 5.14.8 — the spec names this type CancelSessionResponse.  The
-- SGP32- prefix is permanent: SGP.32 replaces the SGP.22 branches with a compact
-- form, so the two are different types sharing one C namespace (see the note
-- above SGP32-EUICCInfo2).  The spec's CancelSessionOk is an empty SEQUENCE just
-- like the SGP.22 one, so the imported type is used directly.
-- ASN1START
SGP32-CancelSessionResponse ::= [65] CHOICE { -- Tag 'BF41' — spec name is CancelSessionResponse; see the note above
  cancelSessionResponseOk CancelSessionResponseOk,
  cancelSessionResponseError INTEGER {invalidTransactionId(5), undefinedError(127)},
  compactCancelSessionResponseOk CompactCancelSessionResponseOk
}
CompactCancelSessionResponseOk ::= SEQUENCE {
  compactEuiccCancelSessionSigned CompactEuiccCancelSessionSigned, -- Compact version of euiccCancelSessionSigned
  euiccCancelSessionSignature [APPLICATION 55] OCTET STRING -- tag 5F37 signature on euiccCancelSessionSigned
}
CompactEuiccCancelSessionSigned ::= SEQUENCE {
  reason CancelSessionReason OPTIONAL
}
-- ASN1STOP

-- Section 6.3.1
-- ASN1START
EsipaMessageFromIpaToEim ::= CHOICE {
  initiateAuthenticationRequestEsipa [57] InitiateAuthenticationRequestEsipa, -- Tag 'BF39'
  authenticateClientRequestEsipa [59] AuthenticateClientRequestEsipa, -- Tag 'BF3B'
  getBoundProfilePackageRequestEsipa [58] GetBoundProfilePackageRequestEsipa, -- Tag 'BF3A'
  cancelSessionRequestEsipa [65] CancelSessionRequestEsipa, -- Tag 'BF41'
  handleNotificationEsipa [61] HandleNotificationEsipa, -- Tag 'BF3D'
  transferEimPackageResponse [78] TransferEimPackageResponse, -- Tag 'BF4E'
  getEimPackageRequest [79] GetEimPackageRequest, -- Tag 'BF4F'
  provideEimPackageResult [80] ProvideEimPackageResult -- Tag 'BF50'
}
EsipaMessageFromEimToIpa ::= CHOICE {
  initiateAuthenticationResponseEsipa [57] InitiateAuthenticationResponseEsipa, -- Tag 'BF39'
  authenticateClientResponseEsipa [59] AuthenticateClientResponseEsipa, -- Tag 'BF3B'
  getBoundProfilePackageResponseEsipa [58] GetBoundProfilePackageResponseEsipa, -- Tag 'BF3A'
  cancelSessionResponseEsipa [65] CancelSessionResponseEsipa, -- Tag 'BF41'
  transferEimPackageRequest [78] TransferEimPackageRequest, -- Tag 'BF4E'
  getEimPackageResponse [79] GetEimPackageResponse, -- Tag 'BF4F'
  provideEimPackageResultResponse [80] ProvideEimPackageResultResponse -- Tag 'BF50'
}
-- ASN1STOP

-- Section 6.3.2
-- UPDATE for v1.1: 5.14.1 / 6.3.2.1 — InitiateAuthenticationRequestEsipa adds
-- eimTransactionId [2]; InitiateAuthenticationErrorEsipa adds
-- invalidEimTransactionId(52) and undefinedError(127).
-- UPDATE for v1.1: 6.3.2.1 — InitiateAuthenticationOkEsipa.euiccCiPKIdToBeUsed
-- renamed to euiccCiPKIdentifierToBeUsed.
-- esipa_init_auth.c populates eimTransactionId and reads the renamed field;
-- both are covered by tests/esipa_bindings.
-- ASN1START
InitiateAuthenticationRequestEsipa ::= [57] SEQUENCE { -- Tag 'BF39'
  euiccChallenge [1] Octet16, -- random eUICC challenge
  smdpAddress [3] UTF8String OPTIONAL,
  euiccInfo1 EUICCInfo1 OPTIONAL,
  eimTransactionId [2] TransactionId OPTIONAL -- NEW in v1.1: 5.14.1 / 6.3.2.1
}
InitiateAuthenticationResponseEsipa ::= [57] CHOICE { -- Tag 'BF39'
  initiateAuthenticationOkEsipa InitiateAuthenticationOkEsipa,
  initiateAuthenticationErrorEsipa INTEGER {
    invalidDpAddress(1),
    euiccVersionNotSupportedByDp(2),
    ciPKIdNotSupported(3),
    smdpAddressMismatch(50),
    smdpOidMismatch(51),
    invalidEimTransactionId(52), -- NEW in v1.1: 6.3.2.1
    undefinedError(127)          -- NEW in v1.1: 6.3.2.1
  }
}
InitiateAuthenticationOkEsipa ::= SEQUENCE {
  transactionId [0] TransactionId OPTIONAL, -- The TransactionID generated by the SM-DP+
  serverSigned1 ServerSigned1, -- Signed information
  serverSignature1 [APPLICATION 55] OCTET STRING, -- Server Sign1, Tag '5F37'
  euiccCiPKIdentifierToBeUsed OCTET STRING, -- UPDATE for v1.1: 6.3.2.1 — renamed from euiccCiPKIdToBeused
  serverCertificate Certificate,
  matchingId UTF8String OPTIONAL,
  ctxParams1 [2] CtxParams1 OPTIONAL
}
-- ASN1STOP

-- Section 6.3.2.2
-- UPDATE for v1.1: 6.3.2.2 — the spec writes this field's type as plain
-- AuthenticateServerResponse, meaning its own local definition; here that is
-- SGP32-AuthenticateServerResponse, which is the same type under the prefix the
-- flat C namespace forces (see the note above SGP32-EUICCInfo2).
-- UPDATE for v1.1: 6.3.2.2 — error label profileMetadataMismatch renamed
-- to metadataMismatch in GetBoundProfilePackageResponseEsipa (§6.3.2.3).
-- ASN1START
AuthenticateClientRequestEsipa ::= [59] SEQUENCE { -- Tag 'BF3B'
  transactionId [0] TransactionId,
  authenticateServerResponse [56] SGP32-AuthenticateServerResponse -- This is the response from ES10b.AuthenticateServer, possibly in compact format
}
AuthenticateClientResponseEsipa ::= [59] CHOICE { -- Tag 'BF3B'
  authenticateClientOkDPEsipa AuthenticateClientOkDPEsipa,
  authenticateClientOkDSEsipa AuthenticateClientOkDSEsipa,
  authenticateClientErrorEsipa INTEGER {
    eumCertificateInvalid(1),
    eumCertificateExpired(2),
    euiccCertificateInvalid(3),
    euiccCertificateExpired(4),
    euiccSignatureInvalid(5),
    matchingIdRefused(6),
    eidMismatch(7),
    noEligibleProfile(8),
    ciPKUnknown(9),
    invalidTransactionId(10),
    insufficientMemory(11),
    pprNotAllowed(50),
    eventIdUnknown(56),
    undefinedError(127)
  }
}
AuthenticateClientOkDPEsipa ::= SEQUENCE {
  transactionId [0] TransactionId OPTIONAL,
  profileMetaData [37] StoreMetadataRequest OPTIONAL,
  smdpSigned2 SmdpSigned2, -- Signed information
  smdpSignature2 [APPLICATION 55] OCTET STRING, -- Tag '5F37'
  smdpCertificate Certificate, -- CERT.DPpb.ECDSA
  hashCc Octet32 OPTIONAL -- Hash of confirmation code
}
AuthenticateClientOkDSEsipa ::= SEQUENCE {
  transactionId [0] TransactionId, -- v1.2: mandatory (not OPTIONAL)
  profileDownloadTrigger [84] ProfileDownloadTriggerRequest OPTIONAL -- Tag 'BF54'
}
-- ASN1STOP

-- Section 6.3.2.3
-- ASN1START
GetBoundProfilePackageRequestEsipa ::= [58] SEQUENCE { -- Tag 'BF3A'
  transactionId [0] TransactionId,
  prepareDownloadResponse [33] SGP32-PrepareDownloadResponse -- This is the response from ES10b.PrepareDownload, possibly in compact format
}
GetBoundProfilePackageResponseEsipa ::= [58] CHOICE { -- Tag 'BF3A'
  getBoundProfilePackageOkEsipa GetBoundProfilePackageOkEsipa,
  getBoundProfilePackageErrorEsipa INTEGER {
    euiccSignatureInvalid(1),
    confirmationCodeMissing(2),
    confirmationCodeRefused(3),
    confirmationCodeRetriesExceeded(4),
    bppRebindingRefused(5),
    downloadOrderExpired(6),
    metadataMismatch(50), -- UPDATE for v1.1: 6.3.2.3 — renamed from profileMetadataMismatch
    invalidTransactionId(95),
    undefinedError(127)
  }
}
GetBoundProfilePackageOkEsipa ::= SEQUENCE {
  transactionId [0] TransactionId OPTIONAL,
  boundProfilePackage [54] BoundProfilePackage
}
-- ASN1STOP

-- Section 6.3.2.4
-- UPDATE for v1.1: 6.3.2.4 — HandleNotificationEsipa restructured.  pendingNotification
-- now has explicit tag [0] and uses PendingNotification (kept as SGP32-PendingNotification
-- alias locally).  provideEimPackageResult now tagged [80].
-- ASN1START
HandleNotificationEsipa ::= [61] CHOICE { -- Tag 'BF3D'
  pendingNotification [0] SGP32-PendingNotification, -- UPDATE for v1.1: 6.3.2.4 — tag [0] added
  provideEimPackageResult [80] ProvideEimPackageResult -- UPDATE for v1.1: 6.3.2.4 — tag [80] added; Tag 'BF50'
}
-- ASN1STOP

-- Section 6.3.2.5
-- ASN1START
CancelSessionRequestEsipa ::= [65] SEQUENCE { -- Tag 'BF41'
  transactionId TransactionId,
  cancelSessionResponse SGP32-CancelSessionResponse -- This is the response from ES10b.CancelSession function, possibly in compact format
}
CancelSessionResponseEsipa ::= [65] CHOICE { -- Tag 'BF41'
  cancelSessionOk CancelSessionOk,
  cancelSessionError INTEGER {
    invalidTransactionId(1),
    euiccSignatureInvalid(2),
    undefinedError(127)
  }
}
-- ASN1STOP


-- Section 6.3.2.6
-- NEW in v1.1: 6.3.2.6 — StateChangeCause type.
-- UPDATE for v1.1: 5.14.5 — GetEimPackageRequest adds stateChangeCause [1];
-- rPLMN moves to [2].
-- UPDATE for v1.1: 6.3.2.6 — GetEimPackageResponse.eimPackageError adds
-- eidNotFound(2), invalidEid(3), missingEid(4).
-- stateChangeCause is populated by esipa_get_eim_pkg.c from ipa_esipa_note_state_change().
-- ASN1START
StateChangeCause ::= INTEGER { -- NEW in v1.1: 6.3.2.6
  otherEim(0),              -- change(s) requested by another registered eIM
  fallback(1),              -- following fallback requested by IPA
  emergencyProfile(2),      -- following Emergency Profile swap requested by IPA
  local(3),                 -- applied locally (RFU, not supported in this version)
  reset(4),                 -- following an eUICC reset
  immediateEnableProfile(5),-- following immediate Profile enabling by IPA
  deviceChange(6),          -- detected by IPAe following IoT Device change (removable eSIMs)
  undefined(127)
}
GetEimPackageRequest ::= [79] SEQUENCE { -- Tag 'BF4F'
  eidValue [APPLICATION 26] Octet16, -- Tag '5A'
  notifyStateChange [0] NULL OPTIONAL, -- Notification to the eIM that it should update its information
  stateChangeCause [1] StateChangeCause OPTIONAL, -- NEW in v1.1: 5.14.5 — cause of notified state change(s)
  rPLMN [2] OCTET STRING (SIZE(3)) OPTIONAL -- UPDATE for v1.1: 6.3.2.6 — tag changed from [1] to [2]; supplied by the host via ipa_set_rplmn()
}
GetEimPackageResponse ::= [79] CHOICE { -- Tag 'BF4F'
  euiccPackageRequest [81] EuiccPackageRequest, -- Tag 'BF51'
  ipaEuiccDataRequest [82] IpaEuiccDataRequest, -- Tag 'BF52'
  profileDownloadTriggerRequest [84] ProfileDownloadTriggerRequest, -- Tag 'BF54'
  eimPackageError INTEGER {
    noEimPackageAvailable(1),
    eidNotFound(2),   -- NEW in v1.1: 6.3.2.6
    invalidEid(3),    -- NEW in v1.1: 6.3.2.6
    missingEid(4),    -- NEW in v1.1: 6.3.2.6
    undefinedError(127)
  }
}
-- ASN1STOP

-- Section 6.3.2.7
-- UPDATE for v1.1: 5.14.6 / 6.3.2.7 — ProvideEimPackageResult restructure.
-- Was a CHOICE at top level; now a SEQUENCE containing eidValue OPTIONAL and
-- eimPackageResult EimPackageResult (which is now the CHOICE).
-- New wrapper types: EimPackageResultErrorCode, EimPackageResultResponseError.
-- UPDATE for v1.2: CR111003R00 — removed eimPackageResultErrorCode from top-level
-- EimPackageResult; error now carried by eimPackageResultResponseError [0] wrapper.
-- UPDATE for v1.2: CR111002R00 — ProvideEimPackageResultResponse gains
-- provideEimPackageResultError with eidNotFound(2), invalidEid(3), missingEid(4).
-- UPDATE for v1.2: CR12014R02 — clarified when EidValue is included: section
-- 5.14.6 NOTE 1 makes it required whenever the eIM has no other way to identify
-- the eUICC, so esipa_prvde_eim_pkg_rslt.c always sends it.
-- The rework these notes called for is done: the SEQUENCE wrapper, the
-- eimPackageResultResponseError branch, the notificationList tag [0] and the
-- three-branch ProvideEimPackageResultResponse are all implemented there.
-- ASN1START
EimPackageResultErrorCode ::= INTEGER { -- NEW in v1.1: 6.3.2.7
  invalidPackageFormat(1),
  unknownPackage(2),
  undefinedError(127)
}
EimPackageResultResponseError ::= SEQUENCE { -- NEW in v1.1: 6.3.2.7
  eimTransactionId [0] TransactionId OPTIONAL,
  eimPackageResultErrorCode EimPackageResultErrorCode
}
EimPackageResult ::= CHOICE { -- NEW in v1.1: 6.3.2.7 — promoted to named type
  euiccPackageResult [81] EuiccPackageResult, -- Tag 'BF51'
  ePRAndNotifications SEQUENCE {
    euiccPackageResult [81] EuiccPackageResult, -- Tag 'BF51'
    notificationList [0] SGP32-PendingNotificationList -- UPDATE for v1.1: 6.3.2.7 — tag [0] with SGP32-PendingNotificationList (was [43] SGP32-RetrieveNotificationsListResponse)
  },
  ipaEuiccDataResponse [82] IpaEuiccDataResponse, -- Tag 'BF52'
  profileDownloadTriggerResult [84] ProfileDownloadTriggerResult, -- Tag 'BF54'
  eimPackageResultResponseError [0] EimPackageResultResponseError -- NEW in v1.1: 6.3.2.7 — replaces old eimPackageError INTEGER branch
}
ProvideEimPackageResult ::= [80] SEQUENCE { -- Tag 'BF50' — UPDATE for v1.1: 6.3.2.7 — restructured from CHOICE to SEQUENCE
  eidValue [APPLICATION 26] Octet16 OPTIONAL, -- NEW in v1.1: 6.3.2.7 — Tag '5A'
  eimPackageResult EimPackageResult
}
ProvideEimPackageResultResponse ::= [80] CHOICE { -- Tag 'BF50' — UPDATE for v1.1: 6.3.2.7 — was SEQUENCE; now CHOICE
  eimAcknowledgements [83] EimAcknowledgements, -- Tag 'BF53'
  emptyResponse SEQUENCE {}, -- NEW in v1.1: 6.3.2.7 — because EimAcknowledgements was OPTIONAL
  provideEimPackageResultError INTEGER { -- NEW in v1.2: CR111002R00
    eidNotFound(2),
    invalidEid(3),
    missingEid(4),
    undefinedError(127)
  }
}
-- ASN1STOP

-- Section 6.3.3.1
-- UPDATE for v1.1: 6.3.3.1 — TransferEimPackageResponse.notificationList uses
-- SGP32-PendingNotificationList (tag [0]) instead of SGP32-RetrieveNotificationsListResponse.
-- ASN1START
TransferEimPackageRequest ::= [78] CHOICE { -- Tag 'BF4E'
  euiccPackageRequest [81] EuiccPackageRequest, -- Tag 'BF51'
  ipaEuiccDataRequest [82] IpaEuiccDataRequest, -- Tag 'BF52'
  eimAcknowledgements [83] EimAcknowledgements, -- Tag 'BF53'
  profileDownloadTriggerRequest [84] ProfileDownloadTriggerRequest -- Tag 'BF54'
}
TransferEimPackageResponse ::= [78] CHOICE { -- Tag 'BF4E'
  euiccPackageResult [81] EuiccPackageResult, -- Tag 'BF51'
  ePRAndNotifications SEQUENCE {
    euiccPackageResult [81] EuiccPackageResult, -- Tag 'BF51'
    notificationList [0] SGP32-PendingNotificationList -- UPDATE for v1.1: 6.3.3.1 — was [43] SGP32-RetrieveNotificationsListResponse
  },
  ipaEuiccDataResponse [82] IpaEuiccDataResponse, -- Tag 'BF52'
  eimPackageReceived NULL,
  eimPackageError INTEGER {
    invalidPackageFormat(1),
    unknownPackage(2),
    undefinedError(127)
  }
}
-- ASN1STOP


END
